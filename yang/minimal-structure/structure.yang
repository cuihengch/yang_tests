module example-structure {
    yang-version 1.1;
    namespace "urn:example:structure";
    prefix ex;

    import ietf-yang-structure-ext {
        prefix sx;
    }

    sx:structure address-book {
        list address {
            key "last first";
            leaf last {
                type string;
                description "Last name";
            }
            leaf first {
                type string;
                description "First name";
            }
            leaf street {
                type string;
                description "Street name";
            }
            leaf city {
                type string;
                description "City name";
            }
            leaf state {
                type string;
                description "State name";
            }
        }
    }

    container test {
        leaf abc {
            type string;
        }
    }
}
