module example {
    yang-version 1.1;
    namespace "urn:example";
    prefix ex;

    container my-payload {
      description
        "The message payload content.";

      leaf data-type {
        type string;
        description
          "Type of data carried in the payload.";
      }

      leaf content {
        type string;
        description
          "The actual content of the payload.";
      }
    }
}
